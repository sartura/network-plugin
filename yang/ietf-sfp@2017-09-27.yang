module ietf-sfp {
  namespace "urn:ietf:params:xml:ns:yang:ietf-sfp";
  prefix sfp;

  import ietf-interfaces {
    prefix if;
  }
  import ietf-inet-types {
    prefix inet;
  }
  import ietf-yang-types {
    prefix yang;
  }

  organization "DT";

  description
    "SFP";

  augment "/if:interfaces-state" {
    description
      "Data nodes for the operational state of SFP on interfaces.";
    container ddm {
//      presence "Present if SFP is enabled on this interface";
      config false;
      description
        ".";
      leaf rx-pwr {
        type decimal64 {
             fraction-digits 4;
        }
        description
          "";
      }
      leaf tx-pwr {
        type decimal64 {
             fraction-digits 4;
        }
        description
          "";
      }
      leaf current {
        type decimal64 {
             fraction-digits 4;
        }
        description
          "";
      }
      leaf voltage {
        type decimal64 {
             fraction-digits 4;
        }
        description
          "";
      }
    }
  }
}
