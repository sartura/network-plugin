module wireless {

    namespace "urn:terastream:wireless";

    prefix "terastream-wireless";

    organization
        "Deutsche Telekom AG";

    contact
        "Hmm";

    description
        "This module defines wireless used in the TeraStream home gateway project.";

    revision "2017-08-08" {
        description
            "Version 0.1.0 -- Initial version.";
    }


    container "devices" {
      description
        "Wireless devices.";

      list device {

        key "name";

        leaf name {
          type string;
        }

        leaf type {
           type string;
           default "broadcom";
        }

        leaf country {
             type string;
             default "EU/13";
        }

        leaf band {
             type string;
             default "a";
        }

        leaf bandwidth {
             type int32;
             default "80";
        }

        leaf scantimer {
             type int32;
             default "15";
        }

        leaf wmm  {
             type int32;
             default "1";
        }

        leaf wmm_noack {
             type int32;
             default "0";
        }

        leaf wmm_apsd {
             type int32;
             default "1";
        }

        leaf txpower {
             type int32;
             default "100";
        }

        leaf rateset {
             type string;
             default "default";
        }

        leaf frag {
             type int32;
             default "2346";
        }

        leaf rts {
             type int32;
             default "2347";
        }
        
        leaf dtim_period {
             type int32;
             default "1";
        }
        
        leaf beacon_int {
             type int32;
             default "100";
        }
        
        leaf rxchainps {
             type int32;
             default "0";
        }

        leaf rxchainps_qt {
             type int32;
             default "10";
        }

        leaf rxchainps_pps {
             type int32;
             default "10";
        }

        leaf rifs {
             type int32;
             default "0";
        }

        leaf rifs_advert {
             type int32;
             default "0";
        }

        leaf maxassoc {
             type int32;
             default "32";
        }

        leaf beamforming {
             type int32;
             default "1";
        }

        leaf doth {
             type int32;
             default "1";
        }

        leaf dfsc {
             type int32;
             default "1";
        }

        leaf channel {
             type string;
             default "auto";
        }

        leaf disabled {
             type int32;
             default "0";
        }

        leaf hwmode {
             type string;
             default "11ac";
        }

        list interface {
            key "ssid";

            description
              "List of configured interfaces on device";

            unique "index";

            leaf device {
                 type string;
                 default "wl0";
            }

            leaf index {
                 type int32;
                  default "0";
            }

            leaf network {
                 type string;
                 default "lan";
            }

            leaf mode {
                 type string;
                 default "ap";
            }

            leaf ssid {
                 type string;
                 default "PANTERA-7858";
            }

            leaf encryption {
                 type string;
                 default "psk2";
            }

            leaf cipher {
                 type string;
                 default "auto";
            }

            leaf key {
                 type string;
                 default "SUBA6AXU3A7YKJ";
            }

            leaf gtk_rekey {
                 type string;
                 default "3600";
            }

            leaf macfilter {
                 type string;
                 default "0";
            }

            leaf wps_pbc {
                 type string;
                 default "1";
            }

            leaf wmf_bss_enable {
                 type string;
                 default "1";
            }

            leaf bss_max {
                 type string;
                 default "32";
            }

            leaf ifname {
                 type string;
                 default "wl0";
            }

          }
      }
    }
}
