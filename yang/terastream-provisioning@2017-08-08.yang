module terastream-provisioning {

    namespace "urn:terastream:provisioning";

    prefix "ts-sip";

    organization
        "Deutsche Telekom AG";

    description
        "This module defines HGW provisioning used in the TeraStream home gateway project.";

    revision "2017-08-08" {
        description
            "Version 0.1.0 -- Initial version.";
    }

    container "hgw-diagnostics" {
      config false;

      description
        "Device diagnostics.";

       leaf "version" {
           type "string";
       }

       leaf "memory-status" {
            type "uint32";
       }

       leaf "cpu-usage" {
            type "uint32";
       }
    }
}
